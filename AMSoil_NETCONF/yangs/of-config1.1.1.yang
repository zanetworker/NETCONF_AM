module of-config1.1.1 {
  namespace "urn:onf:of111:config:yang";
  prefix of11-config;

  import ietf-yang-types { prefix yang; }
  import ietf-inet-types { prefix inet; }

  organization "ONF Config Management Group";

  contact "tbd";

  description "

    NETCONF Operational Considerations

    Elements that are configurable, optional and have a default
    value MAY be reported by replies to NETCONF <get-config>
    requests. All non-configurable values SHOULD be reported by
    replies to NETCONF <get> requests.

     Attemps to modify non-configurable elements with a NETCONF
     <edit-config> operation MUST result in an
     'operation-not-supported' error with type 'application'.

     When validating an <edit‑config> operation the following 
     errors MUST be detected:

     * Delete requests for non-existent data. In this case a
       'data-missing' error is returned.
     * Create requests for existent data. In this case a 
       'data-exists' error is returned.
     * If the NETCONF operation creates data nodes under a
        'choice', any existing nodes from other branches are
        deleted.";

  revision 2011-12-07 {
    description "First Version";

    reference "tbd";
  }



/*****************************************************************
 * Groupings
 *****************************************************************/



  grouping OFLogicalSwitchType {
    description "This grouping specifies all properties of an
      OpenFlow Logical Switch.

      Elements of type OFLogicalSwitchType cannot be created or
      deleted with NETCONF <edit-config> operations 'create' or
      'delete'. The other NETCONF <edit-config> operations MUST be
      implemented as follows: 

      * The 'id' element MUST be present at all <edit-config>
        operations to identify the OpenFlow Logical Switch.
      * If the operation is 'merge' or 'replace', and the element
        does not exist, a 'data-missing' error is returned. If the
        element exists its value is set to the value found in the
        XML RPC data.
      * If the operation is 'create', a 'operation-not-supported'
        error with type 'application' is returned.
      * If the operation is 'delete', 'operation-not-supported'
        error with type 'application' is returned.";
    leaf id {
      type OFConfigId;
      mandatory true;
      description "A unique but locally arbitrary identifier that
        identifies a Logical Switch within the context of an
        OpenFlow Capable Switch. It MUST be persistent across
        reboots of the OpenFlow Capable Switch.

        This element MUST be present to identify the OpenFlow
        Logical Switch.";
    }
    container capabilities {
      config false;
      description "This element contains all capability items that
        an OpenFlow Logical Switch MAY implement.

        This element and its children can only be retrieved by
        NETCONF <get> operation since it contain no configuration
        data.";
      uses OFLogicalSwitchCapabilitiesType;
    }
    leaf datapath-id {
      type datapath-id-type;
      mandatory true;
      description "The datapath identifier of the Logical Switch
        that uniquely identifies this Logical Switch within the
        context of all OpenFlow Controllers associated with the
        OpenFlow Logical Switch.  The datapath identifier is a
        string value that MUST be formatted as a sequence of 8
        2-digit hexadecimal numbers that are separated by colons,
        for example, '01:23:45:67:89:ab:cd:ef'.  When processing a
        datapath identifier, the case of the decimal digits MUST be
        ignored.

        This element MUST be present in the NETCONF data store.
        If this element is not present in a NETCONF <edit-config>
        operation 'create', 'merge' or 'replace' and the parent
        element does not exist, a 'data-missing' error is
        returned.";
    }
    leaf enabled {
      type boolean;
      default false;
      description "This element indicates the administrative state
        of the OpenFlow Logical Switch.  A value of 'false' means
        the OpenFlow Logical Switch MUST NOT communicate with any 
        OpenFlow Controllers, MUST NOT conduct any OpenFlow 
        processing, and SHOULD NOT be utilizing computational or 
        network resources of the underlying platform.

        This element is optional. If this element is not present it
        defaults to 'false'.";
    }
    leaf check-controller-certificate {
      type boolean;
      default false;
      description "This element indicates the behavior of the 
        OpenFlow Logical Switch when connecting to an OpenFlow
        Controller.  
      
        If set to value 'false', the logical switch will connect to
        a controller without checking any controller certificate.  
      
        If set to value 'true', then the logical switch will
        connect to a controller with element <protocol> set to
        'TLS', only if the controller provides a certificate that
        can be verified with one of the certificates stored in the
        list called external-certificates in the OpenFlow Capable
        Switch.  
      
        If a certificate cannot be validated, the OpenFlow Logical 
        Switch MUST terminate communication with the corresponding
        OpenFlow Controller, MUST NOT conduct any OpenFlow
        processing on requests of this OpenFlow controller, and 
        SHOULD NOT further utilize any computational or network 
        resources of for dealing with this connection.
      
        If set to value 'true', the OpenFlow Logical Switch MUST
        NOT connect to any OpenFlow Controller that does not
        provide a certificate. This implies that it cannot connect
        to an OpenFlow controller that has the value of element
        protocol set to 'TCP'. Only connections with protocol 'TLS'
        are possible in this case.

        This element is optional. If this element is not present it
        defaults to 'false'.";
    }
    leaf lost-connection-behavior {
      type enumeration {
        enum failSecureMode;
        enum failStandaloneMode;
      }
      default failSecureMode;
      description "This element indicates the the behavior of the 
        OpenFlow Logical Switch in case it loses contact with all 
        OpenFlow Controllers.  There are two alternative modes in
        such a case: fails secure mode and fail standalone mode as
        defined by the OpenFlow protocol specification version 1.2,
        section 6.4.  These are the only allowed values for this
        element. Default is the fail secure mode.

        This element is optional. If this element is not present it
        defaults to 'failSecureMode'.";
    }
    container controllers {
      description "The list of controllers for this Logical switch.

        The element 'id' of OFControllerType MUST be unique within
        this list.";
      list controller {
        key "id";
        description "The list of OpenFlow Controllers that are 
          assigned to the OpenFlow Logical Switch.  The switch MUST
          NOT connect to any OpenFlow Controller that is not
          contained in this list.

          NETCONF <edit-config> operations MUST be implemented as 
          follows: 

          * The 'id' element MUST be present at all <edit-config>
            operations to identify the controller.
          * If the operation is 'merge' or 'replace', the element
            is created if it does not exist, and its value is set
            to the value found in the XML RPC data.
          * If the operation is 'create', the element is created if
            it does not exist. If the element already exists, a
            'data‑exists' error is returned.
          * If the operation is 'delete', the element is deleted if
            it exists. If the element does not exist, a 
            'data‑missing' error is returned.";
        uses OFControllerType;
      }
    }
    container resources {
      description "The list of identifiers of all resources of the
        OpenFlow Capable Switch that the OpenFlow Logical Switch
        has exclusive or non-exclusive access to.  A resource is 
        identified by the value of its resource-identifier element.
        For each resource identifier value in this list, there MUST
        be an element with a matching resource identifier value in 
        the resources list of the OpenFlow Capable Switch.
      
        Identifiers of this list are contained in elements
        indicating the type of resource: 'port', 'queue',
        'certificate', or 'flow-table'.  Depending on the type,
        different constraints apply.  These are specified in
        separate descriptions per type.

        At present the elements in this lists are not configurable
        and can only be retrieved by NETCONF <get> or <get-config>
        operations. Attemps to modify this element and its children
        with a NETCONF <edit-config> operation MUST result in an 
        'operation-not-supported' error with type 'application'.";
      leaf-list port {
        type leafref {
          path "/capable-switch/resources/port/resource-id";
        }
        description "A resource identifier of a port of the 
          OpenFlow Capable Switch that the OpenFlow Logical Switch
          has exclusive access to.

          The elements in this list MUST refer to elements at the
          following path:
            /capable-switch/resources/port/resource-id

          Elements in this list MUST be unique. This means each
          port element can only be referenced once.";
      }
      leaf-list queue {
        type leafref {
          path "/capable-switch/resources/queue/resource-id";
        }
        description "A resource identifier of a queue of the
          OpenFlow Capable Switch that the OpenFlow Logical Switch
          has exclusive access to.

          The elements in this list MUST refer to elements at the
          following path:
            /capable-switch/resources/queue/resource-id

          Elements in this list MUST be unique. This means each
          queue element can only be referenced once.";
      }
      leaf certificate {
        type leafref {
          path "/capable-switch/resources/owned-certificate/resource-id";
        }
        description "The resource identifier of the owned
          certificate in the OpenFlow Capable Switch that the
          OpenFlow Logical Switch uses to identify itself.  This
          element MUST NOT occur more than once in an OpenFlow
          Logical Switch's resource list.  
        
          If no such element is in an OpenFlow Logical Switch's 
          resource list, then the OpenFlow Logical Switch does not 
          authenticate itself towards an OpenFloe Controller with a
          certificate.  If this element is present, then the
          OpenFlow Logical Switch MUST provide this certificate for
          authentication to an OpenFlow Controller when setting up
          a TLS connection.  
        
          For TCP connections this element is irrelevant.

          The element MUST refer to an element at the following
          path:
            /capable-switch/resources/owned-certificate/resource-id
          ";
      }
      leaf-list flow-table {
        type leafref {
          path "/capable-switch/resources/flow-table/resource-id";
        }
        description "A resource identifier of a flow table of the 
          OpenFlow Capable Switch that the OpenFlow Logical Switch 
          has exclusive access to.

          The elements in this list MUST refer to elements at the
          following path:
            /capable-switch/resources/flow-table/resource-id

          Elements in this list MUST be unique. This means each
          flow-table element can only be referenced once.";
      }
    }
  }

  grouping OFLogicalSwitchCapabilitiesType {
    description "This grouping specifies all properties of an
      OpenFlow logical switch's capabilities.

      Elements in the type OFLogicalSwitchCapabilitiesType are not
      configurable and can only be retrieved by NETCONF <get>
      operations. Attemps to modify this element and its children
      with a NETCONF <edit-config> operation MUST result in an 
      'operation-not-supported' error with type 'application'.";
    leaf max-buffered-packets {
      type uint32;
      description "The maximum number of packets the logical switch
        can buffer when sending packets to the controller using
        packet-in messages.";
    }
    leaf max-tables {
      type uint8;
      description "The number of flow tables supported by the
        logical switch.";
    }
    leaf max-ports {
      type uint32;
      description "The number of flow tables supported by the
        logical switch.";
    }
    leaf flow-statistics {
      type boolean;
      default false;
      description "Specifies if the logical switch supports flow
        statistics.";
    }
    leaf table-statistics {
      type boolean;
      default false;
      description "Specifies if the logical switch supports table
        statistics.";
    }
    leaf port-statistics {
      type boolean;
      default false;
      description "Specifies if the logical switch supports port
        statistics.";
    }
    leaf group-statistics {
      type boolean;
      default false;
      description "Specifies if the logical switch supports group
        statistics.";
    }
    leaf queue-statistics {
      type boolean;
      default false;
      description "Specifies if the logical switch supports queue
        statistics.";
    }
    leaf reassemble-ip-fragments {
      type boolean;
      default false;
      description "Specifies if the logical switch supports
        reassemble IP fragments.";
    }
    leaf block-looping-ports {
      type boolean;
      default false;
      description "'true' indicates that a switch protocol outside
        of OpenFlow, such as 802.1D Spanning Tree, will detect
        topology loops and block ports to prevent packet loops.";
    }
    container reserved-port-types {
      description "Specify generic forwarding actions such as
        sending to the controller, flooding, or forwarding using
        non-OpenFlow methods, such as 'normal' switch processing.";
      reference "The types of reserved ports are defined in
         OpenFlow Switch Specification versions 1.2, 1.3, and
         1.3.1.";
      leaf-list type {
        type enumeration {
          enum all;
          enum controller;
          enum table;
          enum inport;
          enum any;
          enum normal;
          enum flood;
        }
      }
    }
    container group-types {
      description "Specify the group types supported by the logical
        switch.";
      reference "The types of groups are defined in OpenFlow Switch
        Specification versions 1.2, 1.3, and 1.3.1.";
      leaf-list type {
        type enumeration {
          enum all;
          enum select;
          enum indirect;
          enum fast-failover;
        }
      }
    }
    container group-capabilities {
      description "Specify the group capabilities supported by the
        logical switch.";
      reference "The types of group capability are defined in
        OpenFlow Switch Specification versions 1.2, 1.3, and
        1.3.1.";
      leaf-list capability {
        type enumeration {
          enum select-weight;
          enum select-liveness;
          enum chaining;
          enum chaining-check;
        }
      }
    }
    container action-types {
      description "Specify the action types supported by the
        logical switch.";
      leaf-list type {
        type OFActionType;
      }
    }
    container instruction-types {
      description "Specify the instruction types supported by the
        logical switch.";
      leaf-list type {
        type OFInstructionType;
      }
    }
  }

  grouping OFControllerType {
    description "This grouping specifies all properties of an
      OpenFlow Logical Switch Controller.

      NETCONF <edit-config> operations MUST be implemented as 
      follows: 

      * The 'id' element MUST be present at all <edit-config>
        operations to identify the controller.
      * If the operation is 'merge' or 'replace', the element is
        created if it does not exist, and its value is set to the
        value found in the XML RPC data.
      * If the operation is 'create', the element is created if it
        does not exist. If the element already exists, a
        'data‑exists' error is returned.
      * If the operation is 'delete', the element is deleted if it
        exists. If the element does not exist, a 'data‑missing'
        error is returned.";
    leaf id {
      type OFConfigId;
      mandatory true;
      description "A unique but locally arbitrary identifier that
        uniquely identifies an OpenFlow Controller within the
        context of an OpenFlow Capable Switch.  It MUST be
        persistent across reboots of the OpenFlow Capable Switch.

        This element MUST be present to identify the OpenFlow
        controller.";
    }
    leaf role {
      type enumeration {
        enum master;
        enum slave;
        enum equal;
      }
      default equal;
      description "This element indicates the role of the OpenFlow 
        Controller.  Semantics of these roles are specified in the 
        OpenFlow specifications 1.0 - 1.3.1.  It is RECOMMENDED
        that the roles of controllers are not configured by
        OF-CONFIG 1.1.1 but determined using the OpenFlow protocol.
        OpenFlow Controllers configured by OF-CONFIG 1.1.1 have the
        default role 'equal'.  A role other than 'equal' MAY be
        assigned to a controller.  Roles 'slave' and 'equal' MAY be
        assigned to multiple controllers.  Role 'master' MUST NOT
        be assigned to more than one controller.

        This element is optional. If this element is not present it
        defaults to 'equal'.";
    }
    leaf ip-address {
      type inet:ip-address;
      mandatory true;
      description "The IP address of the OpenFlow Controller.  This
        IP address is used by the OpenFlow Logical Switch when
        connecting to the OpenFlow Controller.

        This element MUST be present in the NETCONF data store.
        If this element is not present in a NETCONF <edit-config>
        operation 'create', 'merge' or 'replace' and the parent
        element does not exist, a 'data-missing' error is
        returned.";
    }
    leaf port {
      type inet:port-number;
      default 6633;
      description "The TCP port number at the OpenFlow Controller.
        This port number is used by the OpenFlow Logical Switch
        when connecting to the OpenFlow Controller using TCP or
        TLS.  The default value is 6633.

        This element is optional. If this element is not present it
        defaults to 6633.";
    }
    leaf local-ip-address {
      type inet:ip-address;
      description "The local IP address of the OpenFlow Logical
        Switch when connecting to this OpenFlow Controller.  It is
        the source IP address of packets sent to this OpenFlow
        Controller.  If present, this element overrides any default
        IP address.
    
        
        This element is optional. Attempts to set this element to
        an IP address that cannot be used by the OpenFlow Logical
        Switch MUST result in an 'bad-element' error with type
        'application'. The <error-info> element MUST contain the
        name of this element in the <bad-element> element.";
    }
    leaf local-port {
      type inet:port-number;
      description "The local TCP port number of the OpenFlow
        Logical Switch when connecting to this OpenFlow Controller.
        It is the source TCP port number of packets sent to this
        OpenFlow Controller.  If this element is not present, then
        the port number is chosen arbitrarily by the OpenFlow
        Logical Switch.
      
        This element is optional. Attempts to set this element to a
        port number that cannot be used by the OpenFlow Logical
        Switch MUST result in an 'bad-element' error with type
        'application'. The <error-info> element MUST contain the
        name of this element in the <bad-element> element.";
    }
    leaf protocol {
      type enumeration {
        enum "tcp";
        enum "tls";
      }
      default "tls";
      description "The default protocol tha the OpenFlow Logical 
        Switch uses to connect to this OpenFlow Controller.  'tls'
        is the default value.

        This element is optional. If this element is not present it
        defaults to 'tls'.";
    }
    container state {
      config false;
      description "This container holds connection state
        information that indicate the connection state of the
        OpenFlow Logical Switch and the OpenFlow protocol version
        used for the connection.

        Children of this element are not configurable and can only
        be retrieved by NETCONF <get> operations. Attemps to modify
        this element and its children with a NETCONF <edit-config>
        operation MUST result in an 'operation-not-supported' error
        with type 'application'.";
      leaf connection-state {
        type OFUpDownStateType;
        description "This object indicates the connections state of
          the OpenFlow Logical Switch to this controller.";
      }
      leaf current-version {
        type OFOpenFlowVersionType;
        description "This object indicates the version of the
          OpenFlow protocol used between the OpenFlow Logical
          Switch and this Controller.  If element connection-state
          has value 'up', then this element indicates the actual
          version in use.  If element connection-state has value
          'down', then this element indicates the version number of
          the last established connection with this OpenFlow
          Controller.  The value of this element MAY be persistent
          across reboots of the OpenFlow Logical Switch in such a
          case.  If element connection-state has value 'down'and
          there is no information about previous connections to
          this OpenFlow controller, then this element is not
          present or has the value '0'.";
      }
      leaf-list supported-versions {
        type OFOpenFlowVersionType;
        description "This list of elements includes one entry for
          each OpenFlow protocol version that this OpenFlow
          controller supports.  It SHOULD contain all";
      }
      leaf local-ip-address-in-use {
        type inet:ip-address;
        description "The local IP address of the OpenFlow Logical
          Switch when connecting to this OpenFlow Controller.  It
          is the source IP address of packets sent to this OpenFlow
          Controller.  If present, this element overrides any
          default IP address.";
      }
      leaf local-port-in-use {
        type inet:port-number;
        description "The local TCP port number of the OpenFlow
          Logical Switch.  If element connection-state has value
          'up', then this element indicates the actual port number
          in use.  If element connection-state has value 'down',
          then this element indicates the port number used for the
          last attempt to establish a connection with this OpenFlow
          Controller.??? 
          When connecting to this OpenFlow Controller, it is the 
          source TCP port number of packets sent to this OpenFlow 
          Controller.  If this element has its defaqult value 0,
          then port number is chosen arbitrarily by the OpenFlow
          Logical Switch.";
      }
    }
  }

  grouping OFResourceType {
    description "This element specifies a generic OpenFlow resource
      that is used as a basis for specific resources. Even though
      this element is not used on its own the following rules for
      NETCONF operations MUST be obeyed also by elemnts using this
      element.

      NETCONF <edit-config> operations MUST be implemented as 
      follows: 

      * The 'id' element MUST be present at all <edit-config>
        operations to identify the resource.
      * If the operation is 'merge' or 'replace', the element is
        created if it does not exist, and its value is set to the
        value found in the XML RPC data.
      * If the operation is 'create', the element is created if it
        does not exist. If the element already exists, a
        'data‑exists' error is returned.
      * If the operation is 'delete', the element is deleted if it
        exists. If the element does not exist, a 'data‑missing'
        error is returned.";
    leaf resource-id {
      type inet:uri;
      mandatory true;
      description "A unique but locally arbitrary identifier that
        uniquely identifies an OpenFlow Port within the context  
        of an OpenFlow Logical Switch.  It MUST be persistent
        across reboots of the OpenFlow Capable Switch.

        This element MUST be present to identify the OpenFlow
        resource.";
    }
  }

  grouping OFPortBaseTunnelType {
    description "A group of common elements that are included
      in every supported tunnel type.  Tunnels are modeled as 
      logical ports.

      One pair of local/remote endpoints must exist for a tunnel
      configuration.

      Only elements from one choice must exist at a time.";
    choice endpoints {
      mandatory true;
      case v4-endpoints {
        leaf local-endpoint-ipv4-adress {
          type inet:ipv4-address;
          description "The IPv4 address of the local tunnel
            endpoint.";
        }
        leaf remote-endpoint-ipv4-adress {
          type inet:ipv4-address;
          description "The IPv4 address of the remote tunnel
            endpoint.";
        }
      }
      case v6-endpoints {
        leaf local-endpoint-ipv6-adress {
          type inet:ipv6-address;
          description "The IPv6 address of the local tunnel
            endpoint.";
        }
        leaf remote-endpoint-ipv6-adress {
          type inet:ipv6-address;
          description "The IPv6 address of the remote tunnel
            endpoint.";
        }
      }
      case mac-endpoints {
        leaf local-endpoint-mac-adress {
          type yang:mac-address;
          description "The MAC address of the local tunnel
            endpoint.";
        }
        leaf remote-endpoint-mac-adress {
          type yang:mac-address;
          description "The MAC address of the remote tunnel
            endpoint.";
        }
      }
    }
  }

  grouping OFPortIPGRETunnelType {
    description "Properties of a IP-in-GRE tunnel with key,
      checksum, and sequence number information.";
    uses OFPortBaseTunnelType;
    leaf checksum-present {
      type boolean;
      default true;
      description "Indicates presence of the GRE checksum.";
    }
    leaf key-present {
      type boolean;
      default true;
      description "Indicates presence of the GRE key.";
    }
    leaf key {
      when "../key-present='true'" {
        description "This element is only relevant if element 
          key-present of this IP GRE Tunnel has value 'true'.";
      }
      type uint32;
      mandatory true;
      description "The (optional) key of the GRE tunnel.  It MAY
        be used to set the OXM_OF_TUNNEL_ID match field metadata 
        in the OpenFlow protocol";
    }
    leaf sequence-number-present {
      type boolean;
      default false;
      description "Indicates presence of the GRE sequence
        number.";
    }
  }

  grouping OFPortVXLANTunnelType {
    description "Properties of a VxLAN tunnel.";
    uses OFPortBaseTunnelType;
    leaf vni-valid {
      type boolean;
      default true;
      description "Indicates how the corresponding flag should be
        set in packets sent on the tunnel.";
    }
    leaf vni {
      type uint32;
      description "Virtual network identifier assigned to all
        packets sent on the tunnel.  A VxLAN  implementation MAY 
        use the this element to set the OXM_OF_TUNNEL_ID match 
        field metadata in the OpenFlow protocol.";
    }
    leaf vni-multicast-group {
      type inet:ip-address;
      description "If IP multicast is used to support broadcast
        on the tunnel this specifies the corresponding multicast
        IP address";
    }
    leaf udp-source-port {
      type inet:port-number;
      description "Specifies the outer UDP source port number.
        If this element is absent, the port number MAY be chosen 
        dynamically.";
    }
    leaf udp-dest-port {
      type inet:port-number;
      description "Specifies the outer UDP destination port
        number.  It is intended to reserve a port number for
        VxLAN at IANA.  As soon as this has been reserved, the
        reserved number SHOULD become the default value for this
        element.";
    }
    leaf udp-checksum {
      type boolean;
      default false;
      description "Boolean flag to indicate whether or not the
        outer UDP checksum should be set";
    }
  }
 
  grouping OFPortNVGRETunnelType {
    description "Properties of a NVGRE tunnel.";
    uses OFPortBaseTunnelType;
    leaf tni {
      type uint32;
      description "Specifies the tenant network identifier
        assigned to all packets sent on the tunnel";
    }
    leaf tni-resv {
      type uint32;
      description "Used to set the reserved user-defined bits of
        the GRE key field";
    }
    leaf tni-multicast-group {
      type inet:ip-address;
      description "If IP multicast is used to support broadcast
        on the tunnel this element specifies the corresponding 
        multicast IP address";
    }
  }

  grouping OFPortType {
    description "This element specifies all properties of an
      OpenFlow resource of type OpenFlow Port. It represent a
      physical port or a logical port of the OpenFlow Capable
      Switch and can be assigned for exclusive use to an OpenFlow
      Logical Switch.  A logical port represents a tunnel endpoint
      as described in the OpenFlow protocol specification versions
      1.3 - 1.3.1.

      NETCONF <edit-config> operations MUST be implemented as 
      follows: 

      * The 'resource-id' element of OFResoureType MUST be present
        at all <edit-config> operations to identify the port.
      * If the operation is 'merge' or 'replace', the element is
        created if it does not exist, and its value is set to the
        value found in the XML RPC data.
      * If the operation is 'create', the element is created if it
        does not exist. If the element already exists, a
        'data‑exists' error is returned.
      * If the operation is 'delete', the element is deleted if it
        exists. If the element does not exist, a 'data‑missing'
        error is returned.";
    uses OFResourceType;
    leaf number {
      type uint64;
      config false;
      description "This number identifies the OpenFlow Port to 
        OpenFlow Controllers. It is assigned to an OpenFlow Port 
        latest when the OpenFlow Port is associated with and
        OpenFlow Logical Switch.  If the OpenFlow Port is
        associated with an OpenFlow Logical Switch, this element
        MUST be unique within the context of the OpenFlow Logical
        Switch.  
      
        OpenFlow Capable Switch implementations may choose to
        assign values to OpenFlow Ports that are unique within the
        context of the OpenFlow Logical Switch.  These numbers can
        be used independent of assignments to OpenFlow Logical
        Switches. 
      
        Other implementations may assign values to this element
        only if the OpenFlow Port is assigned to an OpenFlow
        Logical Switch.  If no value is currently assigned to this
        element then this element MUST NOT be included in replies
        to NETCONF <get> requests. Since this element is not
        configurable with the NETCONF protocol it MUST NOT be
        included in replies to NETCONF <get-config> requests.";
    }
    leaf name {
      type string { length "1..16"; }
      config false;
      description "This element assists OpenFlow Controllers in 
        identifying OpenFlow Ports.  
      
        This element is not to be set by the OP-CONFIG protocol,
        but it is set by the switch implementation.  It may be set
        at start-up time of an OpenFlow Capable Switch or when the 
        OpenFlow Port is assigned to an OpenFlow Logical Switch.
        It MAY also be not set at all.  If this element is set to a
        value other than the empty string when being assigned to an
        OpenFlow Logical Switch, then the value of this element
        MUST be unique within the context of the OpenFlow Logical
        Switch.  
      
        If no value or the empty string is currently assigned to
        this element then this element MUST not be included in
        replies to NETCONF <get> requests. Since this element is
        not configurable with the NETCONF protocol it MUST NOT be
        included in replies to NETCONF <get-config> requests.";
    }
    leaf current-rate {
      when "../features/current/rate='other'" {
        description "This element is only valid if the element rate
          of the current features has value 'other'.";
      }
      type uint32;
      units "kbit/s";
      config false;
      description "This element indicates the current bit rate of 
        the port. Its values is to be provided in units of kilobit 
        per second (kbps). This element is only valid if the 
        element called 'rate' in the current Port Features has a 
        value of 'other'.

        Since this element is not configurable with the NETCONF
        protocol it MUST NOT be included in replies to NETCONF
        <get-config> requests.";
    }
    leaf max-rate {
      when "../features/current/rate='other'" {
        description "This element is only valid if the element rate
          of the current features has value 'other'.";
      }
      type uint32;
      units "kbit/s";
      config false;
      description "This element indicates the maximum bit rate of 
        the port. Its values is to be provided in units of kilobit 
        per second (kbps). This element is only valid if the 
        element called 'rate' in the current Port Features has a 
        value of 'other'.

        Since this element is not configurable with the NETCONF
        protocol it MUST NOT be included in replies to NETCONF
        <get-config> requests.";
    }
    container configuration {
      description "This element represents the general
        adminitrative configuration of the OpenFlow Port.";
      leaf admin-state {
        type OFUpDownStateType;
        default 'up';
        description "The administrative state of the port.  If
          true, the port has been administratively brought down and
          SHOULD not be used by OpenFlow.

          This element is optional. If this element is not present
          it defaults to 'up'.";
      }
      leaf no-receive {
        type boolean;
        default false;
        description "If true, packets received at this OpenFlow
          port SHOULD be dropped.

          This element is optional. If this element is not present
          it defaults to 'false'.";
      }
      leaf no-forward {
        type boolean;
        default false;
        description "If true, packets forwarded to this OpenFlow
          port SHOULD be dropped.

          This element is optional. If this element is not present
          it defaults to 'false'.";
      }
      leaf no-packet-in {
        type boolean;
        default false;
        description "If true, packets received on that port that 
          generate a table miss should never trigger a packet-in 
          message to the OpenFlow Controller.

          This element is optional. If this element is not present
          it defaults to 'false'.";
      }
    }
    container state {
      config false;
      description "This element represents the general operational 
      state of the OpenFlow Port.

      Children of this element are not configurable and can only be
      retrieved by NETCONF <get> operations. Attemps to modify this
      element and its children with a NETCONF <edit-config>
      operation MUST result in an 'operation-not-supported' error
      with type 'application'.";
      leaf oper-state {
        type OFUpDownStateType;
        description "If the value of this element is 'down', it 
          indicates that there is no physical link present.";
      }
      leaf blocked {
        type boolean;
        description "If the value of this element is 'true', it 
          indicates that a switch protocol outside of OpenFlow,
          such as 802.1D Spanning Tree, is preventing the use of
          this OpenFlow port for OpenFlow flooding.";
      }
      leaf live {
        type boolean;
        description "If the value of this element is 'true', it 
          indicates that this OpenFlow Port is live and can be used
          for fast failover.";
      }
    }
    container features {
      container current {
        uses OFPortCurrentFeatureListType;
        config false;
        description "The features (rates, duplex, etc.) of the
          port, that are currently in use.

          Children of this element are not configurable and can
          only be retrieved by NETCONF <get> operations. Attemps to
          modify this element and its children with a NETCONF
          <edit-config> operation MUST result in an
          'operation-not-supported' error with type
          'application'.";
      }
      container advertised {
        uses OFPortOtherFeatureListType;
        description "The features (rates, duplex, etc.) of the
          port, that are advertised to the peer port.

          NETCONF <edit-config> operations MUST be implemented as 
          follows: 

          * The 'resource-id' element of OFResoureType MUST be
            present in the path or in the filter at all
            <edit-config> operations to identify the port.
          * If the operation is 'merge' or 'replace', the element
            is created if it does not exist, and its value is set
            to the value found in the XML RPC data.
          * If the operation is 'create', the element is created if
            it does not exist. If the element already exists, a
            'data‑exists' error is returned.
          * If the operation is 'delete', the element is deleted if
            it exists. If the element does not exist, a
            'data‑missing' error is returned.";
      }
      container supported {
        uses OFPortOtherFeatureListType;
        config false;
        description "The features (rates, duplex, etc.) of the
          port, that are supported on the port.

          Children of this element are not configurable and can
          only be retrieved by NETCONF <get> operations. Attemps to
          modify this element and its children with a NETCONF
          <edit-config> operation MUST result in an
          'operation-not-supported' error with type
          'application'.";
      }
      container advertised-peer {
        uses OFPortOtherFeatureListType;
        config false;
        description "The features (rates, duplex, etc.) that are
          currently advertised by the peer port.

          Children of this element are not configurable and can
          only be retrieved by NETCONF <get> operations. Attemps to
          modify this element and its children with a NETCONF
          <edit-config> operation MUST result in an
          'operation-not-supported' error with type
          'application'.";
      }
    }
    choice tunnel-type {
      description "Tunnels are modeled as logical ports.

        Elements in this choice are not configurable and can only
        be retrieved by NETCONF <get> operations. Attemps to modify
        this element and its children with a NETCONF <edit-config>
        operation MUST result in an 'operation-not-supported' error
        with type 'application'.

        Only elements from one choice must exist at a time.";
      container tunnel {
        description "Properties of a basic IP-in-GRE tunnel.";
        uses OFPortBaseTunnelType;
      }
      container ipgre-tunnel {
        description "Properties of a IP-in-GRE tunnel.";
        uses OFPortIPGRETunnelType;
      }
      container vxlan-tunnel {
        description "Properties of a VxLAN tunnel.";
        uses OFPortVXLANTunnelType;
      }
      container nvgre-tunnel {
        description "Properties of a NVGRE tunnel.";
        uses OFPortNVGRETunnelType;
      }
    }
  }

  grouping OFQueueType {
    description "This grouping specifies all properties of a queue
      resource.

      NETCONF <edit-config> operations MUST be implemented as 
      follows: 

      * The 'resource-id' element of OFResoureType MUST be present
        at all <edit-config> operations to identify the port.
      * If the operation is 'merge' or 'replace', the element is
        created if it does not exist, and its value is set to the
        value found in the XML RPC data.
      * If the operation is 'create', the element is created if it
        does not exist. If the element already exists, a
        'data‑exists' error is returned.
      * If the operation is 'delete', the element is deleted if it
        exists. If the element does not exist, a 'data‑missing'
        error is returned.";
    uses OFResourceType;
    leaf id {
      type uint64;
      mandatory true;
      description "This id identifies the OpenFlow Queue to 
        OpenFlow Controllers. It is assigned to an OpenFlow Queue 
        latest when the OpenFlow Queue is associated with and
        OpenFlow Logical Switch.  If the OpenFlow Queue is
        associated with an OpenFlow Logical Switch, this element
        MUST be unique within the context of the OpenFlow Logical
        Switch.  
      
        OpenFlow Capable Switch implementations may choose to
        assign values to OpenFlow Queues that are unique within the
        context of the OpenFlow Logical Switch.  These id can be
        used independent of assignments to OpenFlow Logical
        Switches. 
      
        Other implementations may assign values to this element
        only if the OpenFlow Queue is assigned to an OpenFlow
        Logical Switch.  If no value is currently assigned to this
        element then this element MUST NOT be included in replies
        to NETCONF <get> requests. Since this element is not
        configurable with the NETCONF protocol it MUST NOT be
        included in replies to NETCONF <get-config> requests.";
    }
    leaf port {
      type leafref {
        path "/capable-switch/resources/port/resource-id";
      }
      description "Reference to port resources in the Capable
        Switch.
      
        This element associates an OpenFlow Queue with an OpenFlow 
        Port. If the OpenFlow Queue is associated with an OpenFlow 
        Logical Switch S and this element is present, then it MUST 
        be set to the value of element resource-id of an OpenFlow
        Port which is associated with the OpenFlow Logical Switch
        S.

        The element MUST refer to an element at the following path:
          /capable-switch/resources/port/resource-id";
    }
    container properties {
      description "The queue properties currently configured.";
      leaf min-rate {
        type OFTenthOfAPercentType;
        description "The minimal rate that is reserved for this
          queue in 1/10 of a percent of the actual rate.

          This element is optional. If not present a min-rate is
          not set.";
      }
      leaf max-rate {
        type OFTenthOfAPercentType;
        description "The maximum rate that is reserved for this
          queue in 1/10 of a percent of the actual rate.

          This element is optional. If not present the max-rate is
          not set.";
      }
      leaf-list experimenter {
        type uint32;
        description "A list of experimenter identifiers of queue
          properties used.

          This element is optional.";
      }
    }
  }

  grouping OFPortCurrentFeatureListType {
    description "The current features of a port.

      Elements in the type OFPortCurrentFeatureListType are not
      configurable and can only be retrieved by NETCONF <get>
      operations. Attemps to modify this element and its children
      with a NETCONF <edit-config> operation MUST result in an 
      'operation-not-supported' error with type 'application'.";
    leaf rate {
      type OFPortRateType;
      description "The transmission rate that is currently used.
        The value MUST indicate a valid forwarding rate.  
      
        The current Port Feature set MUST contain this element
        exactly once.  The other Port Feature sets MAY contain this
        element more than once.  If this element appears more than
        once in a Port Feature set than the value MUST be unique
        within the Port Feature set.";
    }
    leaf auto-negotiate { 
      type boolean;
      description "Specifies the administrative state of the 
        forwarding rate auto-negotiation protocol at this OpenFlow
        Port.";
    }
    leaf medium {
      type enumeration {
        enum copper;
        enum fiber;
      }
      description "This element MUST indicate a valid physical
        medium used by the OpenFlow Port.
      
        The current Port Feature set MUST contain this element
        exactly once. The other Port Feature sets MAY contain this
        element more than once. If this element appears more than
        once in a Port Feature set than the value MUST be unique
        within the Port Feature set.";
    }
    leaf pause {
      type enumeration {
        enum unsupported;
        enum symmetric;
        enum asymmetric;
      }
      description "Specifies if pausing of transmission is
        supported at all and if yes if it is asymmetric or
        symmetric.";
    }
  }

  grouping OFPortOtherFeatureListType {
    description "The features of a port that are supported or
      advertised.

      If the elements in the OFPortOtherFeatureListType ares used
      as configurable elements the NETCONF <edit-config> operations
      MUST be implemented as follows: 

      * The 'resource-id' element MUST be present in the path or in
        the filter at all <edit-config> operations to identify the
        resource.
      * If the operation is 'merge' or 'replace', the element is
        created if it does not exist, and its value is set to the
        value found in the XML RPC data.
      * If the operation is 'create', the element is created if it
        does not exist. If the element already exists, a
        'data‑exists' error is returned.
      * If the operation is 'delete', the element is deleted if it
        exists. If the element does not exist, a 'data‑missing'
        error is returned.

      If elements in the type OFPortOtherFeatureListType are used
      in an non-configurable way, they only be retrieved by NETCONF
      <get> operations. Attemps to modify this element and its
      children with a NETCONF <edit-config> operation MUST result
      in an 'operation-not-supported' error with type
      'application'.";
    leaf-list rate {
      type OFPortRateType;
      min-elements 1;
      description "The transmission rate that is supported or
        advertised. Multiple transmissions rates are allowed.

        At least one element MUST be present in the NETCONF data
        store. If none of this elements is are present in a NETCONF
        <edit-config> operation 'create', 'merge' or 'replace' and
        the parent element does not exist, a 'data-missing' error
        is returned.";
    }
    leaf auto-negotiate { 
      type boolean;
      default true;
      description "Specifies if auto-negotiation of transmission
        parameters is enabled for the port.

        This element is optional. If this element is not present it
        defaults to 'true'.";
    }
    leaf-list medium {
      type enumeration {
        enum copper;
        enum fiber;
      }
      min-elements 1;
      description "The transmission medium used by the port.
        Multiple media are allowed.

        At least one element MUST be present in the NETCONF data
        store. If none of this elements is are present in a NETCONF
        <edit-config> operation 'create', 'merge' or 'replace' and
        the parent element does not exist, a 'data-missing' error
        is returned.";
    }
    leaf pause {
      type enumeration {
        enum unsupported;
        enum symmetric;
        enum asymmetric;
      }
      mandatory true;
      description "Specifies if pausing of transmission is
        supported at all and if yes if it is asymmetric or
        symmetric.

        This element MUST be present in the NETCONF data store.
        If this element is not present in a NETCONF <edit-config>
        operation 'create', 'merge' or 'replace' and the parent
        element does not exist, a 'data-missing' error is
        returned.";
    }
  }
  
  grouping OFExternalCertificateType {
    description "This grouping specifies a certificate that can be
      used by an OpenFlow Logical Switch for authenticating a 
      controller when a TLS connection is established.";
    uses OFResourceType;
    leaf certificate {
      type string;
      mandatory true;
      description "An X.509 certificate in DER format base64
        encoded.

        This element MUST be present in the NETCONF data store.
        If this element is not present in a NETCONF <edit-config>
        operation 'create', 'merge' or 'replace' and the parent
        element does not exist, a 'data-missing' error is
        returned.";
    }
  }
  
  grouping OFOwnedCertificateType {
    description "This grouping specifies a certificate and a
      private key. It can be used by an OpenFlow Logical Switch for
      authenticating itself to a controller when a TLS connection
      is established.";
    uses OFResourceType;
    leaf certificate {
      type string;
      mandatory true;
      description "An X.509 certificate in DER format base64
        encoded.

        This element MUST be present in the NETCONF data store.
        If this element is not present in a NETCONF <edit-config>
        operation 'create', 'merge' or 'replace' and the parent
        element does not exist, a 'data-missing' error is
        returned.";
    }
    container private-key {
      uses KeyValueType;
      description "This element contains the private key
        corresponding to the certificate. The private key is
        encoded as specified in XML-Signature Syntax and Processing
        (http://www.w3.org/TR/2001/PR-xmldsig-core-20010820/).  
        Currently the specification only support DSA and RSA keys.

        This element MUST be present in the NETCONF data store.
        If this element is not present in a NETCONF <edit-config>
        operation 'create', 'merge' or 'replace' and the parent
        element does not exist, a 'data-missing' error is
        returned.";
    }
  }
  
  grouping KeyValueType {
    description "The KeyValue element contains a single public key
      that may be useful in validating the signature.

      NETCONF <edit-config> operations MUST be implemented as 
      follows: 

      * Exactly one of the elemenst 'DSAKeyValue' or 'RSAKeyValue'
        all <edit-config> operations.
      * If the operation is 'merge' or 'replace', the element is
        created if it does not exist, and its value is set to the
        value found in the XML RPC data.
      * If the operation is 'create', the element is created if it
        does not exist. If the element already exists, a
        'data‑exists' error is returned.
      * If the operation is 'delete', the element is deleted if it
        exists. If the element does not exist, a 'data‑missing'
        error is returned.";
    choice key-type {
      mandatory true;
      case dsa {
        container DSAKeyValue {
          uses DSAKeyValueType;
        }
      }
      case rsa {
        container RSAKeyValue {
          uses RSAKeyValueType;
        }
      }
    }
  }
  
  grouping DSAKeyValueType {
    description "DSA keys and the DSA signature algorithm are
    specified in 'FIPS PUB 186-2, Digital Signature Standard (DSS),
    U.S. Department of Commerce/National Institute of Standards and
    Technology,
    http://csrc.nist.gov/publications/fips/fips186-2/fips186-2.pdf'.
    DSA public key values can have the following fields:

    P
        a prime modulus meeting the requirements of the standard
        above
    Q
        an integer in the range 2**159 < Q < 2**160 which is a
        prime divisor of P-1
    G
        an integer with certain properties with respect to P and Q
    J
        (P - 1) / Q
    Y
        G**X mod P (where X is part of the private key and not made
        public)
    seed
        a DSA prime generation seed
    pgenCounter
        a DSA prime generation counter

    Parameter J is avilable for inclusion solely for efficiency as
    it is calculatable from P and Q. Parameters seed and
    pgenCounter are used in the DSA prime number generation
    algorithm specified in the above standard. As such, they are
    optional but MUST either both be present or both be absent.
    This prime generation algorithm is designed to provide
    assurance that a weak prime is not being used and it yields a P
    and Q value. Parameters P, Q, and G can be public and common to
    a group of users. They might be known from application context.
    As such, they are optional but P and Q MUST either both appear
    or both be absent. If all of P, Q, seed, and pgenCounter are
    present, implementations are not required to check if they are
    consistent and are free to use either P and Q or seed and
    pgenCounter. All parameters are encoded as base64 values.";
    leaf P {
      when "count(../Q) != 0";
      type binary;
      mandatory true;
      description "This element is optional. It MUST be present in
        the NETCONF data store, if the element 'Q' is present.
        
        If element 'Q' is present in a NETCONF <edit-config>
        operation 'create', 'merge' or 'replace' and this element
        is missing, a 'data-missing' error is returned.";
    }
    leaf Q {
      when "count(../P) != 0";
      type binary;
      mandatory true;
      description "This element is optional. It MUST be present in
        the NETCONF data store, if the element 'P' is present.
        
        If element 'P' is present in a NETCONF <edit-config>
        operation 'create', 'merge' or 'replace' and this element
        is missing, a 'data-missing' error is returned.";
    }
    leaf J {
      type binary;
      description "This element is optional.";
    }
    leaf G {
      type binary;
      description "This element is optional.";
    }
    leaf Y {
      type binary;
      mandatory true;
      description "This element MUST be present in the NETCONF data
        store. If this element is not present in a NETCONF
        <edit-config> operation 'create', 'merge' or 'replace' and
        the parent element does not exist, a 'data-missing' error
        is returned.";
    }
    leaf Seed {
      when "count(../PgenCounter) != 0";
      type binary;
      mandatory true;
      description "This element is optional. It MUST be present in
        the NETCONF data store, if the element 'PgenCounter' is
        present.
        
        If element 'PgenCounter' is present in a NETCONF
        <edit-config> operation 'create', 'merge' or 'replace' and
        this element is missing, a 'data-missing' error is
        returned.";
    }
    leaf PgenCounter {
      when "count(../Seed) != 0";
      type binary;
      mandatory true;
      description "This element is optional. It MUST be present in
        the NETCONF data store, if the element 'Seed' is present.
        
        If element 'Seed' is present in a NETCONF <edit-config>
        operation 'create', 'merge' or 'replace' and this element
        is missing, a 'data-missing' error is returned.";
    }
  }
   
  grouping RSAKeyValueType {
    description "RSA key values have two fields: Modulus and
      Exponent.";
    leaf Modulus {
      type binary;
      mandatory true;
      description "This element MUST be present in the NETCONF data
        store. If this element is not present in a NETCONF
        <edit-config> operation 'create', 'merge' or 'replace' and
        the parent element does not exist, a 'data-missing' error
        is returned.";
    }
    leaf Exponent {
      type binary;
      mandatory true;
      description "This element MUST be present in the NETCONF data
        store. If this element is not present in a NETCONF
        <edit-config> operation 'create', 'merge' or 'replace' and
        the parent element does not exist, a 'data-missing' error
        is returned.";
    }
  }
  
  grouping OFFlowTableType {
    description "Representation of an OpenFlow Flow Table Resource.

      Elements in the type OFFlowTableType are not configurable and
      can only be retrieved by NETCONF <get> operations. Attemps to
      modify this element and its children with a NETCONF
      <edit-config> operation MUST result in an
      'operation-not-supported' error with type 'application'.";
    uses OFResourceType;
    leaf max-entries {
      type uint8;
      description "The maximum number of flow entries supported by
        the flow table.";
    }
    container next-tables {
      leaf-list table-id {
        type inet:uri;
      }
      description "An array of resource-ids of all flow tables that
        can be directly reached from this table using the 
        'goto-table' instruction.";
    }
    container instructions {
      leaf-list type {
        type OFInstructionType;
      }
      description "The list of all instruction types supported by
        the flow table.";
    }
    container matches {
      leaf-list type {
        type OFMatchFieldType;
      }
      description "The list of all match types supported by the
        flow table.";
    }
    container write-actions {
      leaf-list type {
        type OFActionType;
      }
      description "The list of all write action types supported by
        the flow table.";
    }
    container apply-actions {
      leaf-list type {
        type OFActionType;
      }
      description "The list of all apply action types supported by
        the flow table.";
    }
    container write-setfields {
      leaf-list type {
        type OFMatchFieldType;
      }
      description "The list of all 'set-field' action types 
        supported by the table using write actions.";
    }
    container apply-setfields {
      leaf-list type {
        type OFMatchFieldType;
      }
      description "The list of all 'set-field' action types 
        supported by the table using apply actions.";
    }
    container wildcards {
      leaf-list type {
        type OFMatchFieldType;
      }
      description "The list of all fields for which the table 
        supports wildcarding.";
    }
    leaf metadata-match {
      type hex-binary;
      description "This element indicates the bits of the metadata 
        field on which the flow table can match.  It is represented
        as 64-bit integer in hexadecimal digits([0-9a-fA-F]) 
        format.";
    }
    leaf metadata-write {
      type hex-binary;
      description "This element indicates the bits of the metadata 
        field on which flow table can write using the 
        'write-metadata' instruction.  It is represented as 
        64-bit integer in hexadecimal digits([0-9a-fA-F]) format.";
    }
  }
  
/*****************************************************************
 * Main container
 *****************************************************************/

  container capable-switch {
    description "The OpenFlow Capable Switch serves as the root 
      element for an OpenFlow configuration.  It contains logical
      switches and resources that can be assigned to logical
      switches.  It may have relations to OpenFlow Configuration 
      Points.";
    leaf id {
      type inet:uri;
      mandatory true;
      description "A unique but locally arbitrary identifier that
        uniquely identifies a Capable Switch within the context of 
        potential OpenFlow Configuration Points.  It MUST be 
        persistent across reboots of the OpenFlow Capable Switch.

        This element MUST be present in the NETCONF data store.
        If this element is not present in a NETCONF <edit-config>
        operation 'create', 'merge' or 'replace' and the parent
        element does not exist, a 'data-missing' error is
        returned.";
    }
    leaf config-version {
      type string;
      config false;
      description "The maximum supported OF-CONFIG version that is
        supported by the OpenFlow Capable Switch. For switches
        implementing this version of the OF-CONFIG protocol this
        MUST always be 1.1.1.

        This object can be used to identify the OF-CONFIG version
        a capable switch supports beginning with version 1.1.1 of 
        OF-CONFIG. In addtion the supported version can be
        determined by the namespace the OpenFlow Capable Switch
        returns to configuration request of an element (like 
        capable-switch) that is present in all OF-CONFIG versions
        specified so far. This is the only possiblity to identify
        OF-CONFIG versions prior to OF-CONFIG 1.1.1.";
    }
    container configuration-points {
      list configuration-point {
        key "id";
        description "The list of all Configuration Points known to
          the OpenFlow Capable Switch that may manage it using
          OF-CONFIG.

          The element 'id' of OFConfigurationType MUST be unique
          within this list.";
        uses OFConfigurationPointType;
      }
    }
    container resources {
      description "A lists containing all resources of the OpenFlow
        Capable Switch that can be used by OpenFlow Logical
        Switches.  Resources are listed here independent of their
        actual assignment to OpenFlow Logical Switches.  They may
        be available to be assigned to an OpenFlow Logical Switch
        or already in use by an OpenFlow Logical Switch.";
      list port {
        must "features/current/rate != 'other' or " +
          "(count(current-rate) = 1 and count(max-rate) = 1 and " +
          " current-rate > 0 and max-rate > 0)" {
          error-message "current-rate and max-rate must be
            specified and greater than 0 if rate equals 'other'";
          description "current-rate and max-rate can only be
            present if rate = 'other', see corresponding leaf
            descriptions. If rate = 'other', then both leafs must
            be set to values greater than zero.";
        }
        key "resource-id";
        description "The list contains all port resources of the
          OpenFlow Capable Switch.

          The element 'resource-id' of OFPortType MUST be unique
          within this list.";
        uses OFPortType;
      }
      list queue {
        key "resource-id";
        description "The list contains all queue resources of the
          OpenFlow Capable Switch.

          The element 'resource-id' of OFQueueType MUST be unique
          within this list.";
        uses OFQueueType;
      }
      list owned-certificate {
        key "resource-id";
        description "The list contains all owned certificate
          resources of the OpenFlow Capable Switch.

          The element 'resource-id' of OFOwnedCertificateType MUST
          be unique within this list.";
        uses OFOwnedCertificateType;
      }
      list external-certificate {
        key "resource-id";
        description "The list contains all external certificate
          resources of the OpenFlow Capable Switch.

          The element 'resource-id' of OFExternalCertificateType
          MUST be unique within this list.";
        uses OFExternalCertificateType;
      }
      list flow-table {
        key "resource-id";
        description "The list contains all flow table resources of
          the OpenFlow Capable Switch.

          The element 'resource-id' of OFFlowTableType MUST be
          unique within this list.";
        uses OFFlowTableType;
      }
    }
    container logical-switches {
      description "This element contains a list of all OpenFlow 
        Logical Switches available at the OpenFlow Capable
        Switch.";
      list switch {
        key "id";
        description "The list of all OpenFlow Logical Switches on
          the OpenFlow Capable Switch.

          The element 'resource-id' of OFLogicalSwitchType MUST be
          unique within this list.";
        uses OFLogicalSwitchType;
      }
    }
  }
  
}
